Correio-Module DEFINITIONS ::=

BEGIN


TamanhoDeCaixa ::= SEQUENCE {
    -- chooses between measurements
    medida          ENUMERATED { pes, polegadas, jardas},
    
    -- values of measurements, setted as REAL (float, decimal)
    altura          REAL,
    largura         REAL,
    comprimento     REAL}

END
